# requirements

## 기능 요구사항 (Container)

### SWR-01: 인식 (Functional)
카메라 영상에서 속도제한 표지판(30/60/90/120)을 실시간으로 인식한다. 신뢰도가 0.5 이하인 결과는 버리고, 한 프레임에서는 신뢰도가 가장 높은 표지판 1개만 사용한다.

### SWR-02: 확정 (Functional)
최근 5개 프레임 중 같은 표지판이 3개 이상 인식되면 그 표지판을 확정한다.
- 표지판이 인식되지 않은 프레임도 5개에 포함한다.
- 기록된 프레임이 5개가 되기 전(시작 직후)에는 확정하지 않는다.
- 인식 정지 상태(SWR-32)가 되면 인식 기록을 모두 비우고, 인식 정지에서 벗어난 뒤 첫 프레임부터 다시 센다.
- 한두 프레임의 오인식이나 놓침으로 결과가 바뀌지 않아야 한다.

### SWR-03: 제한속도 유지 (Functional)
확정된 제한속도는 표지판이 사라져도 다음 표지판이 확정될 때까지 유지한다. 시작 시에는 0(모름)이다.

### SWR-04: CAN 송신 (Functional)
SWR-32(인식 정지), SWR-34(시작 대기 초과)로 송신을 멈추는 경우와 SWR-33(CAN 장치 없음·송신 오류)으로 송신이 멈춘 경우를 제외하고, SWR-11 메시지를 CAN으로 0.1초(10Hz) 주기로 송신한다.
- 각 송신 간격은 0.1초 ±10ms 이내다.
송신 주기는 추론 주기와 독립이다. 추론이 느려져 프레임 간격이 길어져도 위 간격을 지키고, 매 송신에는 그때까지의 최신 판단 결과를 담는다.

## 인터페이스 요구사항 (Container)

### SWR-11: CAN 메시지 (Functional)
can0, 500 kbit/s, ID 0x100(11비트 표준 ID), 4바이트
- byte0: 제한속도 [km/h] (0: 모름, 30/60/90/120)
- byte1: 지금 보이는 표지판 확정 여부 (최근 5개 프레임이 SWR-02 확정 조건을 만족하면 1, 아니면 0)
- byte2: alive counter (0~255, 255 다음 0)
- byte3: 상태 (0: 준비 중, 1: 정상 동작)
- 각 바이트의 값이 정해진 범위를 벗어나면 (내부 클래스가 0~4 정수가 아니거나 byte0 값이 0/30/60/90/120이 아니면, 또는 확정 여부/상태가 0/1이 아니면) 그 바이트는 0으로 송신한다.

## 성능 요구사항 (Container)

### SWR-21: 처리 속도 (Functional)
첫 인식 결과 이후 모든 프레임 간격이 0.2초 이하(5FPS 이상)이고, 연속한 10초 구간마다 평균 15FPS 이상이다.

### SWR-22: 응답 시간 (Functional)
표지판이 계속 인식되면 처음 인식된 프레임부터 0.5초 이내에 확정되고, 확정 후 다음 송신 주기의 CAN 메시지에 반영된다(0.11초 이내, SWR-04).
- 시작 직후와 인식 정지(SWR-32)에서 벗어난 직후에는 확정까지 0.8초 이내다.
- Rationale: SWR-02(최근 5개 중 3개)와 SWR-21(프레임 간격 0.2초 이하)에서 계산한 값이다.
  - 평소: 처음 인식된 프레임부터 3번째 프레임에서 확정 → 간격 2개 × 0.2초 = 0.4초.
  - 시작 직후·인식 정지 해제 직후: 기록 5개가 쌓여야 하므로 늦어도 5번째 프레임에서 확정 → 간격 4개 × 0.2초 = 0.8초.
  - SWR-02의 N/K를 바꾸면 이 시간 목표를 넘지 않는지 다시 확인한다.

## 안전 요구사항 (Container)

### SWR-31: 생존 확인 (Functional)
alive counter를 송신을 시도할 때마다 1씩 증가시켜(255 다음 0), 수신 측이 메시지 누락을 알 수 있게 한다.
- 송신에 실패한 주기에도 증가시킨다. 그래서 실패한 메시지는 수신 측에서 alive가 건너뛴 것으로 보인다.
- 송신하지 않기로 한 주기(SWR-32 인식 정지, SWR-34 시작 대기 초과)에는 증가시키지 않는다.
- 송신이 실제로 전달됐는지는 송신 측이 판단하지 않는다. 누락과 끊김은 수신 측이 alive와 타임아웃으로 판단한다.

### SWR-32: 인식 정지 (Functional)
마지막 인식 결과(표지판이 없는 결과 포함)가 나온 시각(단조 시계 기준) 이후 1초 이상 새 결과가 없으면 '인식 정지' 상태로 본다. 새 결과가 나오면 인식 정지 상태에서 벗어난다.
- 인식 정지 상태에서는 송신하지 않는다(alive도 증가하지 않음, SWR-31).

### SWR-33: 고장 시 동작 (Functional)
CAN 장치가 없거나 송신에 실패해도 인식은 계속한다.
- 실패한 메시지는 다시 보내지 않는다.
- CAN 장치(can0)가 다시 준비되면 프로그램을 다시 시작하지 않고 0.5초 안에 송신을 재개한다.
- 송신이 멈춘 동안에도 송신 주기 판단과 alive 증가는 계속한다(송신 실패로 본다, SWR-31). 그래서 수신 측은 재개 후 alive가 건너뛴 것으로 누락을 안다.
- Rationale: HIL(2026-11-10): can0을 내렸다 올리면 Raspberry Pi CAN Transmit 블록이 재시작 없이 바로 송신을 재개함을 확인. 이전 문구('재시작할 때까지 중지')를 실제 동작에 맞게 고침.

### SWR-34: 시작 상태 (Functional)
첫 인식 결과가 나오기 전(모델 로딩 중)에는 상태를 '준비 중'(0)으로 송신한다.
- 프로그램 시작 후 10초 안에 첫 결과가 없으면 송신을 멈춘다(시작 대기 초과).
- 시작 대기 초과 뒤에 첫 결과가 나오면 상태를 '정상 동작'(1)으로 하여 송신을 다시 시작한다.

### SWR-35: 운영 조건 (Informational)
프로그램 시작 전에 can0이 OS에서 500 kbit/s로 설정되어 up 상태여야 하고, 버스에는 메시지를 받는(ACK하는) 수신 노드가 있어야 한다.
- 예: ip link set can0 up type can bitrate 500000 restart-ms 100
